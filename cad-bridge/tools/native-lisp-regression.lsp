;; Native regression harness for the existing shared LISP library.
;; Load through AutoCAD's UI; loading only defines functions. No MCP trust bypass.
;; MCPNATIVELISP: all cases; MCPNATIVEGEOMETRY / MCPNATIVEUNICODE: subsets.
;; Fixtures are native model-space objects on one unique layer per run. They are
;; retained and reported by handle for the calling agent's guarded MCP cleanup.
;; No DWG save, deletion, security setting, current layer/style/UCS/view change.
;; Output appends to one ignored releases/native-tests/2026-10-21 result file.

(defun mcpnt:root () "D:/CAD-Automation/team/Projects/cad-bridge")

(defun mcpnt:write (message)
  (princ (strcat "\n" message))
  (if mcpnt:log (write-line message mcpnt:log)))

(defun mcpnt:fail (message)
  (setq mcpnt:failure message)
  (exit))

(defun mcpnt:assert (condition message)
  (if (not condition) (mcpnt:fail message)))

(defun mcpnt:near (actual expected)
  (and (numberp actual) (equal actual expected 1e-7)))

(defun mcpnt:case (name function / result detail)
  (setq mcpnt:failure nil pll:last-error nil result (vl-catch-all-apply function nil))
  (cond
    ((vl-catch-all-error-p result)
      (setq mcpnt:failed (1+ mcpnt:failed)
            detail (strcat "FAIL " name ": "
                     (cond (mcpnt:failure) (pll:last-error)
                           ((vl-catch-all-error-message result))))))
    ((and (listp result) (eq (car result) 'skip))
      (setq mcpnt:skipped (1+ mcpnt:skipped)
            detail (strcat "SKIP " name ": " (cadr result))))
    (T (setq mcpnt:passed (1+ mcpnt:passed)
             detail (strcat "PASS " name (if (= (type result) 'STR) (strcat ": " result) "")))))
  (mcpnt:write detail))

(defun mcpnt:track (object label / entity handle)
  (setq entity (if (= (type object) 'ENAME) object (vlax-vla-object->ename object))
        handle (cdr (assoc 5 (entget entity))))
  (mcpnt:assert handle "Fixture has no native handle")
  (setq *mcp-native-handles* (cons handle *mcp-native-handles*))
  (mcpnt:write (strcat "FIXTURE " label " " handle))
  entity)

(defun mcpnt:rx (/ object)
  (setq object (vlax-create-object "VBScript.RegExp"))
  (vlax-put-property object 'Global :vlax-true)
  (vlax-put-property object 'IgnoreCase :vlax-false)
  (setq mcpnt:com (cons object mcpnt:com))
  object)

(defun mcpnt:polyline (label vertices closed / coordinates vertex array object index)
  ;; Fixture input consists of ((x y bulge) ...), not a measurement algorithm.
  (foreach vertex vertices
    (setq coordinates (append coordinates (list (car vertex) (cadr vertex)))))
  (setq array (vlax-make-safearray vlax-vbDouble (cons 0 (1- (length coordinates)))))
  (vlax-safearray-fill array coordinates)
  (setq object (vla-AddLightWeightPolyline mcpnt:model array))
  (mcpnt:track object label)
  (vla-put-Layer object mcpnt:layer)
  (vla-put-Elevation object 0.0)
  (vla-put-Closed object (if closed :vlax-true :vlax-false))
  (setq index 0)
  (foreach vertex vertices
    (vla-SetBulge object index (caddr vertex))
    (setq index (1+ index)))
  (vlax-vla-object->ename object))

(defun mcpnt:text (label text position multiline / object)
  (setq object
    (if multiline
      (vla-AddMText mcpnt:model (vlax-3d-point position) 0.0 text)
      (vla-AddText mcpnt:model text (vlax-3d-point position) 10.0)))
  (mcpnt:track object label)
  (vla-put-Layer object mcpnt:layer)
  (vla-put-StyleName object "Standard")
  (vla-put-Height object 10.0)
  (vla-put-Color object 3)
  object)

(defun mcpnt:leader (label text arrow tail / array object)
  (setq array (vlax-make-safearray vlax-vbDouble '(0 . 5)))
  (vlax-safearray-fill array (append arrow tail))
  (setq object (vla-AddMLeader mcpnt:model array 0))
  (mcpnt:track object label)
  (vla-put-Layer object mcpnt:layer)
  (vla-put-ContentType object 2)
  (vla-put-TextStyleName object "Standard")
  (vla-put-TextHeight object 10.0)
  (vla-put-TextString object text)
  (vla-put-Color object 3)
  object)

(defun mcpnt:geometry-straight (/ poly segments)
  (setq poly (mcpnt:polyline "OPEN_3_4" '((1000.0 1000.0 0.0)
                (1003.0 1000.0 0.0) (1003.0 1004.0 0.0)) nil)
        segments (pll:segments poly))
  (mcpnt:assert (= (length segments) 2) "Expected two native segments")
  (mcpnt:assert (and (mcpnt:near (nth 2 (car segments)) 3.0)
                     (mcpnt:near (nth 2 (cadr segments)) 4.0))
    "PLLENLEADERS segment reader did not return lengths 3 and 4")
  "Native curve distances: 3 and 4")

(defun mcpnt:geometry-closed (/ poly segments handles handle object values)
  (setq poly (mcpnt:polyline "CLOSED_RECT_UI_PLLEN" '((1020.0 1000.0 0.0)
        (1023.0 1000.0 0.0) (1023.0 1004.0 0.0) (1020.0 1004.0 0.0)) T)
        segments (pll:segments poly))
  (mcpnt:assert (= (length segments) 4) "Expected all four closed-rectangle segments")
  (mcpnt:assert (equal (mapcar '(lambda (item) (nth 2 item)) segments)
                       '(3.0 4.0 3.0 4.0) 1e-7)
    "Closed-rectangle lengths differ from 3,4,3,4")
  (setq handles (pllen:label poly 2.5))
  (foreach handle handles
    (setq object (vlax-ename->vla-object (handent handle)))
    (mcpnt:track object "PLLEN_CLOSED_LABEL")
    (vla-put-Layer object mcpnt:layer)
    (setq values (append values (list (atof (vla-get-TextString object))))))
  (mcpnt:assert (equal values '(3.0 4.0 3.0 4.0) 1e-7)
    "PLLEN did not create the four closure labels 3,4,3,4")
  "Both standalone implementations cover all four native edges; actual PLLEN label writer verified")

(defun mcpnt:geometry-arc (/ poly data legacy actual segments)
  (setq poly (mcpnt:polyline "FIRST_BULGE_1" '((1040.0 1000.0 1.0)
        (1050.0 1000.0 0.0) (1050.0 1005.0 0.0)) nil)
        data (get-lwpoly-pts-bulges (entget poly))
        legacy (seglen (caar data) (cadar data) (caadr data))
        actual (vlax-curve-getDistAtParam poly 1.0)
        segments (pll:segments poly))
  (mcpnt:write (strcat "DETAIL first arc native=" (rtos actual 2 9)
                       " PLLEN=" (rtos legacy 2 9)
                       " PLLENLEADERS=" (rtos (nth 2 (car segments)) 2 9)))
  (mcpnt:assert (mcpnt:near (nth 2 (car segments)) actual)
    "PLLENLEADERS arc reader disagrees with native curve length")
  (mcpnt:assert (mcpnt:near legacy actual)
    "PLLEN bulge association disagrees with native arc length")
  "Both existing readers agree with native semicircle length")

(defun mcpnt:netlen (/ nl:rx nl:layers nl:totals nl:issues nl:count objects object sum)
  (setq nl:rx (mcpnt:rx) nl:layers (vla-get-Layers mcpnt:doc) nl:count 0)
  (setq objects (list
    (mcpnt:leader "NETLEN_OPEN" "DN/ID500 L=12.5" '(1000.0 1030.0 0.0) '(1005.0 1035.0 0.0))
    (mcpnt:leader "NETLEN_CLOSED_CASING" "DN/ID500 L=7,5 футляр D700 закрытая прокладка"
      '(1020.0 1030.0 0.0) '(1025.0 1035.0 0.0))
    (mcpnt:leader "NETLEN_WITHOUT_CASING" "DN/ID500 L=2 без футляра"
      '(1040.0 1030.0 0.0) '(1045.0 1035.0 0.0))
    (mcpnt:leader "NETLEN_AMBIGUOUS" "DN/ID500 D600 L=4"
      '(1060.0 1030.0 0.0) '(1065.0 1035.0 0.0))))
  (foreach object objects (nl:consume object))
  (setq sum (apply '+ (mapcar 'cdr nl:totals)))
  (mcpnt:assert (and (= nl:count 3) (= (length nl:totals) 2)
                     (= (length nl:issues) 1) (mcpnt:near sum 22.0))
    (strcat "NETLEN native text parser/grouping mismatch: "
            (vl-prin1-to-string (list nl:count nl:totals nl:issues))))
  (nl:run mcpnt:layer)
  (mcpnt:assert (and *netlen-result*
    (vl-string-search (strcat (nl:format 22.0) " м") *netlen-result*))
    "NETLEN layer scan did not report total 22")
  (mcpnt:write (strcat "DETAIL NETLEN " *netlen-result*))
  "Three counted, one ambiguous, two groups, total 22")

(defun mcpnt:pllenleaders (/ pll:rx pll:layers pll:last-error poly leader plan geometry before)
  (setq pll:rx (mcpnt:rx) pll:layers (vla-get-Layers mcpnt:doc)
        poly (mcpnt:polyline "LEADER_LENGTH_3" '((1080.0 1000.0 0.0)
          (1083.0 1000.0 0.0) (1083.0 1004.0 0.0)) nil)
        leader (mcpnt:leader "LEADER_LENGTH_WRITE" "DN/ID500 L=99,5п.м."
          '(1081.5 1000.0 0.0) '(1082.5 1002.0 0.0))
        before (vla-get-TextString leader)
        geometry (bwuc:geometry (vlax-vla-object->ename leader))
        plan (pll:plan (vlax-vla-object->ename leader) (pll:segments poly) 0.1))
  (mcpnt:assert (= (caddr plan) "DN/ID500 L=3,0п.м.")
    (strcat "Unexpected existing PLLENLEADERS plan: " (vl-prin1-to-string plan)))
  ;; Exercise the existing plan on the actual native annotation, not a text stub.
  (vla-put-TextString (car plan) (caddr plan))
  (mcpnt:assert (= (vla-get-TextString leader) "DN/ID500 L=3,0п.м.")
    "Native leader did not retain planned segment length")
  (mcpnt:assert (equal geometry (bwuc:geometry (vlax-vla-object->ename leader)) 1e-8)
    "PLLENLEADERS text setter changed leader geometry/color")
  (setq plan (pll:plan (vlax-vla-object->ename leader) (pll:segments poly) 0.1))
  (mcpnt:assert (= (cadr plan) (caddr plan)) "Repeated plan is not idempotent")
  "Existing native arrow matching/plan + actual text write; interactive selection/Undo still manual")

(defun mcpnt:pllenleaders-refusal (/ pll:rx pll:layers pll:last-error poly leader before result)
  (setq pll:rx (mcpnt:rx) pll:layers (vla-get-Layers mcpnt:doc)
        poly (mcpnt:polyline "LEADER_VERTEX_REFUSAL" '((1100.0 1000.0 0.0)
          (1103.0 1000.0 0.0) (1103.0 1004.0 0.0)) nil)
        leader (mcpnt:leader "LEADER_AMBIGUOUS_VERTEX" "DN500 L=99 м"
          '(1103.0 1000.0 0.0) '(1105.0 1002.0 0.0))
        before (vla-get-TextString leader)
        result (vl-catch-all-apply 'pll:plan
          (list (vlax-vla-object->ename leader) (pll:segments poly) 0.1)))
  (mcpnt:assert (and (vl-catch-all-error-p result) pll:last-error
                     (= before (vla-get-TextString leader)))
    "Arrow at a vertex was not refused unchanged")
  (strcat "Native arrow-at-vertex refused: " pll:last-error))

(defun mcpnt:unicode (/ objects handles first second object heights geometries index height leader leader-points leader-base)
  (setq objects (list
    (mcpnt:text "UNICODE_TEXT" "Native Unicode DBText" '(1000.0 1080.0 0.0) nil)
    (mcpnt:text "UNICODE_MTEXT" "Native Unicode MText" '(1020.0 1080.0 0.0) T)
    (mcpnt:leader "UNICODE_MLEADER" "Native Unicode MLeader"
      '(1040.0 1080.0 0.0) '(1045.0 1085.0 0.0))))
  (setq leader (last objects)
        leader-points (pll:array (vla-GetLeaderLineVertices leader 0))
        leader-base (cdr (assoc 10 (entget (vlax-vla-object->ename leader)))))
  (foreach object objects
    (setq handles (append handles (list (vla-get-Handle object)))
          geometries (append geometries (list (bwuc:geometry (vlax-vla-object->ename object))))))
  (setq first (bw:apply-unicode handles (strcat (mcpnt:root) "/lisp/OpenSans-CondensedLight.ttf")))
  (mcpnt:write (strcat "DETAIL BWUNICODE_FIRST " (vl-prin1-to-string first)))
  (mcpnt:assert (cdr (assoc 'ok first)) "BWUNICODE native application refused or failed")
  (mcpnt:assert (and
      (equal leader-points (pll:array (vla-GetLeaderLineVertices leader 0)) 1e-8)
      (equal leader-base (cdr (assoc 10 (entget (vlax-vla-object->ename leader)))) 1e-8))
    "MLeader control/base points moved during formatting")
  (setq index 0)
  (foreach object objects
    (setq height (if (= (vla-get-ObjectName object) "AcDbMLeader")
                   (vla-get-TextHeight object) (vla-get-Height object)))
    (mcpnt:assert (mcpnt:near height 9.0) "TrueType height did not become 9 from 10")
    (mcpnt:assert (= (vla-get-Color object) 3) "Explicit native color changed")
    (mcpnt:assert (equal (nth index geometries)
                       (bwuc:geometry (vlax-vla-object->ename object)) 1e-8)
      "Native Unicode operation changed geometry/color")
    (setq heights (append heights (list height)) index (1+ index)))
  (setq second (bw:apply-unicode handles (strcat (mcpnt:root) "/lisp/OpenSans-CondensedLight.ttf")))
  (mcpnt:write (strcat "DETAIL BWUNICODE_REPEAT " (vl-prin1-to-string second)))
  (mcpnt:assert (cdr (assoc 'ok second)) "BWUNICODE repeat refused or failed")
  (setq index 0)
  (foreach object objects
    (setq height (if (= (vla-get-ObjectName object) "AcDbMLeader")
                   (vla-get-TextHeight object) (vla-get-Height object)))
    (mcpnt:assert (mcpnt:near height (nth index heights)) "Repeat scaled Unicode text again")
    (setq index (1+ index)))
  "Actual DBText/MText/MLeader: TTF 10 -> 9, color/geometry retained, second call unchanged")

(defun mcpnt:unicode-refusals (/ object before result text)
  (foreach text '("Field %<\\AcVar Date>%" "{\\H2x;Inline height}")
    (setq object (mcpnt:text "UNICODE_REFUSAL" text '(1080.0 1080.0 0.0) T)
          before (list (vla-get-TextString object) (vla-get-Height object)
                       (vla-get-StyleName object) (vla-get-Layer object) (vla-get-Color object))
          result (bw:apply-unicode (list (vla-get-Handle object))
                   (strcat (mcpnt:root) "/lisp/OpenSans-CondensedLight.ttf")))
    (mcpnt:write (strcat "DETAIL BWUNICODE_REFUSAL " (vl-prin1-to-string result)))
    (mcpnt:assert (and (not (cdr (assoc 'ok result)))
                       (= (cdr (assoc 'phase result)) "preflight")
                       (not (cdr (assoc 'partial_changes result))))
      "Fields/inline formatting were not refused during preflight")
    (mcpnt:assert (equal before (list (vla-get-TextString object) (vla-get-Height object)
      (vla-get-StyleName object) (vla-get-Layer object) (vla-get-Color object)) 1e-8)
      "Unicode refusal changed the actual native object"))
  "Native field/inline-format targets refused without property changes")

(defun mcpnt:unicode-shx (/ font name style object result)
  (setq font (findfile "txt.shx"))
  (if (not font)
    (list 'skip "No native txt.shx fixture font is available")
    (progn
      (setq name (strcat mcpnt:layer "_SHX")
            style (vla-Add (vla-get-TextStyles mcpnt:doc) name))
      (mcpnt:write (strcat "RESOURCE STYLE " name " HANDLE=" (vla-get-Handle style)))
      (vla-put-FontFile style font)
      (setq object (mcpnt:text "UNICODE_SHX" "Native SHX test" '(1120.0 1080.0 0.0) nil))
      (vla-put-StyleName object name)
      (setq result (bw:apply-unicode (list (vla-get-Handle object))
                     (strcat (mcpnt:root) "/lisp/OpenSans-CondensedLight.ttf")))
      (mcpnt:write (strcat "DETAIL BWUNICODE_SHX " (vl-prin1-to-string result)))
      (mcpnt:assert (and (cdr (assoc 'ok result)) (mcpnt:near (vla-get-Height object) 6.0))
        "Native SHX height did not become 6 from 10")
      "Actual SHX DBText height 10 -> 6; unique fixture style retained/reported")))

(defun mcpnt:finish (/ object)
  (foreach object mcpnt:com (vl-catch-all-apply 'vlax-release-object (list object)))
  (setq mcpnt:com nil)
  (mcpnt:write (strcat "HANDLES " (vl-prin1-to-string (reverse *mcp-native-handles*))))
  (mcpnt:write (strcat "DONE PASS=" (itoa mcpnt:passed) " FAIL=" (itoa mcpnt:failed)
                       " SKIP=" (itoa mcpnt:skipped) "; fixtures retained; DWG not saved"))
  (if mcpnt:log (close mcpnt:log))
  (setq mcpnt:log nil))

(defun mcpnt:run (mode / *error* path file)
  (defun *error* (message)
    (mcpnt:write (strcat "HARNESS ERROR " message))
    (mcpnt:finish)
    (princ))
  (vl-load-com)
  (setq mcpnt:passed 0 mcpnt:failed 0 mcpnt:skipped 0 mcpnt:com nil
        *mcp-native-handles* nil mcpnt:doc (vla-get-ActiveDocument (vlax-get-acad-object))
        mcpnt:model (vla-get-ModelSpace mcpnt:doc)
        mcpnt:layer (strcat "MCP_NATIVE_" (itoa (getvar "MILLISECS"))))
  (setq path (strcat (mcpnt:root) "/releases")) (vl-mkdir path)
  (setq path (strcat path "/native-tests")) (vl-mkdir path)
  (setq path (strcat path "/2026-10-21")) (vl-mkdir path)
  (setq mcpnt:log (open (strcat path "/native-lisp-results.txt") "a" "utf8"))
  (mcpnt:assert mcpnt:log "Could not open the designated native results file")
  (mcpnt:write (strcat "BEGIN " mode " DWG=" (vla-get-FullName mcpnt:doc)
                       " LAYER=" mcpnt:layer " DATE=" (rtos (getvar "DATE") 2 8)))
  (foreach file '("netlen.lsp" "polyline_lengths.lsp" "polyline_lengths_to_leaders.lsp" "apply_unicode_style.lsp")
    (load (strcat (mcpnt:root) "/lisp/" file)))
  (mcpnt:assert (not (tblsearch "LAYER" mcpnt:layer)) "Scratch layer collision")
  (vla-Add (vla-get-Layers mcpnt:doc) mcpnt:layer)
  (mcpnt:write (strcat "LAYER " mcpnt:layer " HANDLE="
    (cdr (assoc 5 (entget (tblobjname "LAYER" mcpnt:layer))))))
  (if (member mode '("all" "geometry"))
    (progn
      (mcpnt:case "straight geometry" 'mcpnt:geometry-straight)
      (mcpnt:case "closed geometry" 'mcpnt:geometry-closed)
      (mcpnt:case "legacy PLLEN first arc" 'mcpnt:geometry-arc)
      (mcpnt:case "NETLEN native annotations" 'mcpnt:netlen)
      (mcpnt:case "PLLENLEADERS native plan/write" 'mcpnt:pllenleaders)
      (mcpnt:case "PLLENLEADERS vertex refusal" 'mcpnt:pllenleaders-refusal)))
  (if (member mode '("all" "unicode"))
    (progn
      (mcpnt:case "Unicode native/repeat" 'mcpnt:unicode)
      (mcpnt:case "Unicode native refusals" 'mcpnt:unicode-refusals)
      (mcpnt:case "Unicode native SHX" 'mcpnt:unicode-shx)))
  (mcpnt:finish)
  (princ))

(defun c:MCPNATIVELISP () (mcpnt:run "all"))
(defun c:MCPNATIVEGEOMETRY () (mcpnt:run "geometry"))
(defun c:MCPNATIVEUNICODE () (mcpnt:run "unicode"))
(princ)
